(defun c:ADDNUM (/ ss i en val add)
  (setvar "cmdecho" 0)
  (if (setq add (getreal "\n輸入要增加的數值 (減法請輸負數): "))
    (progn
      (princ "\n請選取要運算的文字...")
      (if (setq ss (ssget '((0 . "*TEXT"))))
        (repeat (setq i (sslength ss))
          (setq en (entget (ssname ss (setq i (1- i)))))
          (setq val (distof (cdr (assoc 1 en))))
          (if val
            (entmod (subst (cons 1 (rtos (+ val add) 2 1)) (assoc 1 en) en))
          )
        )
      )
    )
  )
  (princ "\n運算完成。")
  (princ)
)
